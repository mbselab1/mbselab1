package Enums{

    enum def Status {Static; Planning; Evolving; Maturing; Implementing; ActiveDevelopment;}
    enum def StatusDevStage {ActiveDevelopment; FutureNeeds; MBSEDeployment;}
    enum def Category {DataAndInteroperability; Process; Procedural; PartProduct;}
    enum def RoadmapMilestone {ProcessArchitecture; ManagementEndorsement; IdentifyStrdTools; DigitalThread; EnterpriseDeployment;}
}
